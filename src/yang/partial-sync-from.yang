/*
                            CISCO SAMPLE CODE LICENSE
                                  Version 1.0
                Copyright (c) 2020 Cisco and/or its affiliates

   These terms govern this Cisco example or demo source code and its
   associated documentation (together, the "Sample Code"). By downloading,
   copying, modifying, compiling, or redistributing the Sample Code, you
   accept and agree to be bound by the following terms and conditions (the
   "License"). If you are accepting the License on behalf of an entity, you
   represent that you have the authority to do so (either you or the entity,
   "you"). Sample Code is not supported by Cisco TAC and is not tested for
   quality or performance. This is your only license to the Sample Code and
   all rights not expressly granted are reserved.
*/
module partial-sync-from {

  namespace "http://example.com/partial-sync-from";
  prefix partial-sync-from;

  import ietf-inet-types {
    prefix inet;
  }
  import tailf-common {
    prefix tailf;
  }
  import tailf-ncs {
    prefix ncs;
  }

  description
    "Bla bla...";

  revision 2016-01-01 {
    description
      "Initial revision.";
  }

  container action {
    tailf:action partial-sync-from {
      tailf:actionpoint partial-sync-from-action;
      input {
        leaf xpath {
          tailf:info "Should be relative to the device config. For example -> ios:interface/GigabitEthernet[name=2]";
          type string;
        }
        leaf device {
          type leafref {
            path "/ncs:devices/ncs:device/ncs:name";
          }
        }
      }
      output {
        leaf result {
          type string;
        }
      }
    }
  }
}
